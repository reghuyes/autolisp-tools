;;; AutoLISP import command for wall_centerlines.csv output.
;;; Command: SKETCH2AEC

(setq *s2a-run-cleanup* nil) ; set to T to run post-import PEDIT join

(defun s2a-trim (s)
  (vl-string-trim " \t\r\n" s)
)

(defun s2a-split (text delimiter / idx parts start)
  (setq parts '()
        start 1)
  (while (setq idx (vl-string-search delimiter text (- start 1)))
    (setq parts (cons (substr text start (- idx (- start 1))) parts)
          start (+ idx 2)))
  (reverse (cons (substr text start) parts))
)

(defun s2a-to-real (s)
  (atof (s2a-trim s))
)

(defun s2a-get-normal (p1 p2 / dx dy len)
  (setq dx (- (car p2) (car p1))
        dy (- (cadr p2) (cadr p1))
        len (distance p1 p2))
  (if (< len 1e-8)
    '(0.0 0.0 0.0)
    (list (/ (- dy) len) (/ dx len) 0.0)
  )
)

(defun s2a-point-add (p1 p2 scale)
  (list (+ (car p1) (* scale (car p2)))
        (+ (cadr p1) (* scale (cadr p2)))
        0.0)
)

(defun s2a-ensure-layer (layerName)
  (if (null (tblsearch "LAYER" layerName))
    (command "_.-LAYER" "_Make" layerName ""))
)

(defun s2a-draw-fallback-wall (p1 p2 thickness layerName / offset n p1a p2a p1b p2b)
  (setq n (s2a-get-normal p1 p2)
        offset (/ thickness 2.0)
        p1a (s2a-point-add p1 n offset)
        p2a (s2a-point-add p2 n offset)
        p1b (s2a-point-add p1 n (- offset))
        p2b (s2a-point-add p2 n (- offset)))
  (setvar "CLAYER" layerName)
  (command "_.PLINE" p1a p2a p2b p1b "_C")
)

(defun s2a-try-aec-wall (p1 p2 layerName wallType / result)
  (setvar "CLAYER" layerName)
  (setq result (vl-catch-all-apply
                 'command
                 (list "_.AECWALLADD" "_Type" wallType "_Points" p1 p2 "")))
  (not (vl-catch-all-error-p result))
)

(defun s2a-build-wall (x1 y1 x2 y2 thickness layerName wallType)
  (setq p1 (list x1 y1 0.0)
        p2 (list x2 y2 0.0))
  (if (> (distance p1 p2) 1e-8)
    (progn
      (s2a-ensure-layer layerName)
      (if (not (s2a-try-aec-wall p1 p2 layerName wallType))
        (s2a-draw-fallback-wall p1 p2 thickness layerName)
      )
    )
  )
)

(defun s2a-import-lines (csvPath / f line row x1 y1 x2 y2 layerName thickness wallType count)
  (setq f (open csvPath "r")
        count 0)
  (if (null f)
    (prompt "\nUnable to open CSV file.")
    (progn
      (read-line f) ; skip header
      (while (setq line (read-line f))
        (setq row (mapcar 's2a-trim (s2a-split line ",")))
        (if (>= (length row) 8)
          (progn
            (setq x1 (s2a-to-real (nth 0 row))
                  y1 (s2a-to-real (nth 1 row))
                  x2 (s2a-to-real (nth 2 row))
                  y2 (s2a-to-real (nth 3 row))
                  layerName (nth 4 row)
                  thickness (s2a-to-real (nth 5 row))
                  wallType (nth 7 row))
            (if (= layerName "") (setq layerName "WALL"))
            (if (<= thickness 0.0) (setq thickness 200.0))
            (if (= wallType "") (setq wallType "Generic"))
            (s2a-build-wall x1 y1 x2 y2 thickness layerName wallType)
            (setq count (+ count 1))
          )
        )
      )
      (close f)
      (if (and *s2a-run-cleanup* (> count 0))
        (vl-catch-all-apply 'command (list "_.PEDIT" "_M" "_L" "" "_J" "" "" ""))
      )
      (prompt (strcat "\nImported wall segments: " (itoa count)))
    )
  )
)

(defun c:SKETCH2AEC (/ csvPath)
  (setq csvPath (getfiled "Select wall_centerlines.csv" "" "csv" 8))
  (if csvPath
    (s2a-import-lines csvPath)
    (prompt "\nNo file selected."))
  (princ)
)

(princ "\nLoaded SKETCH2AEC command. Use SKETCH2AEC to import wall centerlines.")
(princ)
